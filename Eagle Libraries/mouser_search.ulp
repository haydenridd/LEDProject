/******************************************************************************

eagle ulp that bring up a search for ch.mouser.com

based on designlink GUI


******************************************************************************/

#usage "<b>Mouser Part Search</b>\n"
       "<p>"
       "Pop up a dialog for searching parts at mouser.com "
       "Display a list of results and a summary of selected item"
       "<p>"
       "<author>Author: Ricardo Araujo</author>"

#require 6.0000

string MOUSER_API_URL = "http://ch.mouser.com/service/searchapi.asmx?WSDL";

string MOUSER_API_KEY;

string SearchHistory[];

int MOUSER_MAX_RESULTS = 20;		//results per query (mouser API max 50)
int mouser_offset = 0;				//offset to start getting results (by default 0)

string mouser_search_options = "RohsAndInStock"; //<searchOptions>None or Rohs or InStock or RohsAndInStock</searchOptions>  

string post_response;			//reponse from net queries
string post_query;				//xml query to send
string POST_TYPE = "application/soap+xml; charset=utf-8";		//type of post content for SOAP1.2


string SelectedResult = "<h1>Enter search keyword</h1>";		//View of main windows (accepts html)
string keyword ="";			//search string
int InStock = 1;			//flag for searching only in stock products
int ROHS = 1;				//flag for searching only RoHS compliant products
int Selection = 0;			//actual selection of list of results

int number_of_results = 0;	// number of results return by search (issued from xlm response)
int total_results = 0;		// number of total results

string LIST_VIEW_HEADER = "Description\tMouser P/N\tManufacturer\tManufacturer P/N";		//Header for list view

string search_xml_results[] ;		//temp var for storing xml search results

string DetailedView = "";

numeric string ListOfResults[] ;	// List of results separated by \t

string Actual_Search_Status = "";	// Var for displaying actual status of search (0-20 of 300)


string int2str(int i) {
	//convert an int to string for displaying messages and XML generation
	string str;
	sprintf(str, "%d", i);
	return str;
}


void saveapikey(void){
	// save api for future usage
	cfgset("ULP:mouser_search.apikey", MOUSER_API_KEY);
}

void getapikey(void){
	// bring up dialog to enter api key
	dlgDialog ("API Key"){
		dlgLabel("Please enter you API key below");
		dlgLabel("You can get one at http://mouser.com/apihome/");
		dlgTextEdit(MOUSER_API_KEY);
		dlgPushButton("Validate") {
			saveapikey();
			dlgAccept();
		}
		dlgPushButton("Cancel") dlgReject();
		};
}

void savecfg(void){
	// save config, mainly the search history
	cfgset("ULP:mouser_search.SearchHistory", strjoin(SearchHistory, '\t'));
}

void loadcfg(void){
	// load previous config (apikey and search history
	MOUSER_API_KEY = cfgget("ULP:mouser_search.apikey", "none");
	if (MOUSER_API_KEY == "none"){
		getapikey();
	}
	string history = cfgget("ULP:mouser_search.SearchHistory");
	strsplit(SearchHistory, history, '\t');
}

void update_mouser_search_options(void) {
	// update search flasg when tick boxes are changed
	if (InStock && ROHS) mouser_search_options = "RohsAndInStock";
	if (InStock && !(ROHS)) mouser_search_options = "InStock";
	if (!(InStock) && ROHS) mouser_search_options = "Rohs";
	if (!(InStock) && !(ROHS)) mouser_search_options = "None";
}


void check_api(void){
	// checks to see if API is up
	post_query = "<?xml version=\"1.0\" encoding=\"utf-8\"?>\n";
	post_query += "<soap12:Envelope xmlns:xsi=\"http://www.w3.org/2001/XMLSchema-instance\"";
	post_query += " xmlns:xsd=\"http://www.w3.org/2001/XMLSchema\"";
	post_query += " xmlns:soap12=\"http://www.w3.org/2003/05/soap-envelope\">\n";
	post_query += "  <soap12:Body>\n";
	post_query += "    <ServiceStatus xmlns=\"http://api.mouser.com/service\" />\n";
	post_query += "  </soap12:Body>\n";
	post_query += "</soap12:Envelope>\n";

	// send the query
	if (netpost(post_response, MOUSER_API_URL, post_query, 20, POST_TYPE) >= 0) {
		post_response = xmltext(post_response, "soap:Envelope/soap:Body/ServiceStatusResponse/ServiceStatusResult");
		if (post_response != "true") {
				dlgMessageBox("Mouser API service not available");
				exit(EXIT_FAILURE);
			}
		}
	else {
		dlgMessageBox("network error " + neterror());
		exit(EXIT_FAILURE);
		}
}

int perform_search(string search_name, int offset){
	//prepare search query
	post_query = "<?xml version=\"1.0\" encoding=\"utf-8\"?>\n";
	post_query += "<soap12:Envelope xmlns:xsi=\"http://www.w3.org/2001/XMLSchema-instance\" xmlns:xsd=\"http://www.w3.org/2001/XMLSchema\" xmlns:soap12=\"http://www.w3.org/2003/05/soap-envelope\">\n";
	post_query += "  <soap12:Header>\n";
	post_query += "    <MouserHeader xmlns=\"http://api.mouser.com/service\">\n";
	post_query += "      <AccountInfo>\n";
	post_query += "        <PartnerID>" + MOUSER_API_KEY + "</PartnerID>\n";
	post_query += "      </AccountInfo>\n";
	post_query += "    </MouserHeader>\n";
	post_query += "  </soap12:Header>\n";
	post_query += "  <soap12:Body>\n";
	post_query += "    <SearchByKeyword xmlns=\"http://api.mouser.com/service\">\n";
	post_query += "      <keyword>" + search_name + "</keyword>\n";
	post_query += "      <records>" + int2str(MOUSER_MAX_RESULTS) + "</records>\n";
	post_query += "      <startingRecord>" + int2str(offset) + "</startingRecord>\n";
	post_query += "      <searchOptions>" + mouser_search_options + "</searchOptions>\n";
	post_query += "    </SearchByKeyword>\n";
	post_query += "  </soap12:Body>\n";
	post_query += "</soap12:Envelope>\n";


	//TODO check proper neterror and results!!!
	netpost(post_response, MOUSER_API_URL, post_query, 20, POST_TYPE);

	//output("mouser_qry.html", "wb") printf("%s", post_response);

	//get the number of results provided by mouser
	number_of_results = strtol(xmltext(post_response, "soap:Envelope/soap:Body/SearchByKeywordResponse/SearchByKeywordResult/NumberOfResult"));

	if (number_of_results < 1) dlgMessageBox("No results found!");

	total_results = number_of_results + offset;

	Actual_Search_Status = "displaying : " + int2str(offset+1) + " to " + int2str(number_of_results+offset);

	xmlelements(search_xml_results, post_response, "soap:Envelope/soap:Body/SearchByKeywordResponse/SearchByKeywordResult/Parts/MouserPart");

	return number_of_results;
}

void clear_searches(void){
	//reset searches and results, useful when starting new search
	int i;
	mouser_offset = 0;
	number_of_results = 0;
	total_results = 0;
	Selection = 0;
	Actual_Search_Status = "";
	for (i=0; i<MOUSER_MAX_RESULTS; i++){
		ListOfResults[i] = 	"";
		search_xml_results[i] = "";
	}
	
}

void clear_search_list(void){
	//reset search_list for new search
	int i;
	for (i=0; i<MOUSER_MAX_RESULTS; i++){
		ListOfResults[i] = 	"";
		search_xml_results[i] = "";
	}
	
}


void update_list_results(void){
	// updates ListOfResults based on search_xml_results
	//string LIST_VIEW_HEADER = "Description\tMouser P/N\tManufacturer\tManufacturer P/N";
	int i;

	for (i=0; i<number_of_results; i++){
		ListOfResults[i] = 	xmltext(search_xml_results[i], "MouserPart/Description") + "\t" +
							xmltext(search_xml_results[i], "MouserPart/MouserPartNumber") + "\t" +
							xmltext(search_xml_results[i], "MouserPart/Manufacturer") + "\t" + 
							xmltext(search_xml_results[i], "MouserPart/ManufacturerPartNumber");
	}
}

void update_selection_display(void) {
	// updates selection view on window: SelectedResult accepts html
	int i;
	if (Selection >= 0  && number_of_results > 0) {
		int number_prices = 0;
		string pricing = "";
		string pricing_xml[];
		number_prices = xmlelements(pricing_xml, search_xml_results[Selection], "MouserPart/PriceBreaks/Pricebreaks");
		for (i=0; i<number_prices;i++){
			pricing += 	"<tr><td>" + xmltext(pricing_xml[i], "Pricebreaks/Quantity") + "</td>" +
						"<td>" + xmltext(pricing_xml[i], "Pricebreaks/Price") + "</td>" +
						"<td>" + xmltext(pricing_xml[i], "Pricebreaks/Currency") + "</td></tr>";

		}
		SelectedResult = "<h3>"+ xmltext(search_xml_results[Selection], "MouserPart/Description") + "</h3><p></p>" +
							"<table><tr><td><img height=\"200\" width=\"200\"" +
							"src=\"" + xmltext(search_xml_results[Selection], "MouserPart/ImagePath") +"\"></td><td>&nbsp;&nbsp;</td>"
							"<td><table><tr><td width=\"140\"><strong>Category: </strong></td><td width=\"400\">" + 
							xmltext(search_xml_results[Selection], "MouserPart/Category") +"</td></tr>" + 
							"<tr><td><strong>Descrition: </strong></td><td>" +
							xmltext(search_xml_results[Selection], "MouserPart/Description") +"</td></tr>" +
							"<tr><td><strong>Manufacturer: </strong></td><td>" +
							xmltext(search_xml_results[Selection], "MouserPart/Manufacturer") +"</td></tr>" +
							"<tr><td><strong>Manufacturer P/N: </strong></td><td>" +
							xmltext(search_xml_results[Selection], "MouserPart/ManufacturerPartNumber") +"</td></tr>" +
							"<tr><td><strong>Mouser P/N: </strong></td><td>" +
							xmltext(search_xml_results[Selection], "MouserPart/MouserPartNumber") +"</td></tr>" +
							"<tr><td><strong>Availability: </strong></td><td>" +
							xmltext(search_xml_results[Selection], "MouserPart/Availability") +"</td></tr>" +
							"<tr><td><strong>LeadTime: </strong></td><td>" +
							xmltext(search_xml_results[Selection], "MouserPart/LeadTime") +"</td></tr>" +
							"<tr><td><strong>LifecycleStatus: </strong></td><td>" +
							xmltext(search_xml_results[Selection], "MouserPart/LifecycleStatus") +"</td></tr>" +
							"<tr><td><strong>ROHSStatus: </strong></td><td>" +
							xmltext(search_xml_results[Selection], "MouserPart/ROHSStatus") +"</td></tr>" +
							"<tr><td><strong>SuggestedReplacement: </strong></td><td>" +
							xmltext(search_xml_results[Selection], "MouserPart/SuggestedReplacement") +"</td></tr>" +
							"<tr><td colspan=\"2\"><a href=\"" +xmltext(search_xml_results[Selection], "MouserPart/ProductDetailUrl") + "\"><strong>Product Detail</strong></a></td></tr>" +
							"<tr><td colspan=\"2\"><a href=\""+ xmltext(search_xml_results[Selection], "MouserPart/DataSheetUrl") + "\"><strong>Datasheet</strong></a></td></tr>" +
							"</table></td></table><p></p><p></p>" +
							"<table border=\"1\"><tr><th width=\"100\">Qty</th><th width=\"100\">Price</th><th width=\"100\">Currency</th>" +
							pricing +
							"</table>";
	}
	else {
		SelectedResult = "<h1> update view </h1>";
	}
}

loadcfg();

check_api();	//check if API is up if not it will exit automatically


dlgDialog("mouser Part Search") {
	dlgVBoxLayout {
		dlgHBoxLayout dlgSpacing(800);
		dlgHBoxLayout {
			dlgTextView(SelectedResult);
			dlgVBoxLayout dlgSpacing(400);
		}
		dlgListView(LIST_VIEW_HEADER, ListOfResults, Selection){
			if (dlgSelectionChanged()) {
               update_selection_display();
			}
		}
		dlgHBoxLayout {
			dlgCheckBox("Available", InStock) update_mouser_search_options();
			dlgCheckBox("RoHS", ROHS) update_mouser_search_options();
			dlgStretch(1);
			dlgPushButton("&Previous")
				if (mouser_offset > 0){
					mouser_offset -= MOUSER_MAX_RESULTS;
					if (mouser_offset < 0) mouser_offset = 0;
					clear_search_list();
					perform_search(keyword, mouser_offset) ;
					update_list_results();
					Selection = 0;
					update_selection_display();
				}
				else {
					dlgMessageBox("At the beginning of the list");
				}
			dlgLabel(Actual_Search_Status, 1);
			dlgPushButton("&Next")
				if (number_of_results >= (MOUSER_MAX_RESULTS-3)) {  //the -3 is because sometimes mouser return less than max
					mouser_offset += number_of_results;
					clear_search_list();
					perform_search(keyword, mouser_offset);
					update_list_results();
					Selection = 0;
					update_selection_display();
				}
				else
					dlgMessageBox("No more results available");
			dlgVBoxLayout {
				dlgHBoxLayout dlgSpacing(238);
				dlgHBoxLayout {
					dlgSpacing(35);
					dlgPushButton("Change API key"){
						getapikey();
					}
				}
			}
		}
		dlgHBoxLayout {
			dlgStringEdit(keyword, SearchHistory, 20);
			dlgPushButton("+Search") {
				clear_searches();
				perform_search(keyword, mouser_offset) ;
				update_list_results();
				Selection = 0;
				update_selection_display();
            }
            dlgPushButton("close") {
				savecfg();
				dlgReject();
			}
         }
      }
   };
